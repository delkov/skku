(defun c:3dsp  (/ vLst oVar pt txt txtl allpt)
  (setq vLst '("CMDECHO" "OSMODE")
    oVar (mapcar 'getvar vLst))
  (while (and (setq pt (getpoint "\nPick Point: "))
          (setq txt (car (entsel "\nSelect Text level: "))))
     (setq txtl (atof (cdr (assoc 1 (entget txt)))))
     (princ txtl)
     (setq pt (subst txtl (last pt) pt)
       allpt (cons pt allpt)))
  (mapcar 'setvar vLst '(0 0))
  (setq allpt (append (reverse allpt) '("" "" "")))
  (command "_spline")
  (mapcar 'command allpt)
  (mapcar 'setvar vLst oVar)
  (princ))

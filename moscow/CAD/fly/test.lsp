(if (member eq_60 file_list)
          (progn
            (alert "AAAAAAAAAAA")
          (setq true_file_list (append true_file_list (list (strcat (itoa eq_60) "dB"))))
          ); progn
        ); if

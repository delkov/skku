(defun c:DInfo

  (   /  ;;         --=={ Local Functions }==--          ;

         *error*
         _Display
         dxf
         _GetColour
         ;_GetLW
         _GetName
        ; _GetScale   
         PurgeLayer
         _PutDXF
         ss->lst
         _Stringify
         _Text
         _Update

         ;;         --=={ Local Variables }==--          ;

         -pi/4
         5pi/4
         alignment
         attachment
         celst
         cent
         cobj
         code
         data
         doc
         e
         express
         gr
         inter
         layers
         mode
         modelst
         msg
         msglst
         on
         owner
         pi/4
         r
         rad
         spc
         ss
         telst
         tent
         vs
         x

         ;;         --=={ Global Variables }==--         ;
   
         ; DInfo:Mode    -- Global: Function Number
         ; DInfo:cRad    -- Global: Cursor Aperture

  )

  (vl-load-com)
  

 
  ;;-------------------------------------------------------------------------------;;
  ;;                           --=={  Preliminaries  }==--                         ;;
  ;;-------------------------------------------------------------------------------;;

  ; (setq spc
  ;   (vlax-get-property
  ;     (setq doc
  ;       (vla-get-ActiveDocument (vlax-get-acad-object))
  ;     )
  ;     (if (= 1 (getvar 'CVPORT)) 'PaperSpace 'ModelSpace)
  ;   )
  ; )
  
  ; (vlax-for l (vla-get-layers doc)
  ;   (setq layers (cons l layers))
  ;   (if (eq :vlax-true (vla-get-Layeron l))
  ;     (setq on (cons l on))
  ;   )
  ; )  
  
  ; (setq Express
  ;   (and (vl-position "acetutil.arx" (arx))
  ;     (not
  ;       (vl-catch-all-error-p
  ;         (vl-catch-all-apply
  ;           (function (lambda nil (acet-sys-shift-down)))
  ;         )
  ;       )
  ;     )
  ;   )
  ; )

  (setq ModeLst '("DINFO" "LAYISO"))

  (or DInfo:Mode (setq DInfo:Mode 0))
  (or DInfo:cRad (setq DInfo:cRad 25.0))

  (setq Alignment
    (list
      (cons acAlignmentLeft               "Left"          )
      (cons acAlignmentCenter             "Center"        )
      (cons acAlignmentRight              "Right"         )
      (cons acAlignmentAligned            "Aligned"       )
      (cons acAlignmentMiddle             "Middle"        )
      (cons acAlignmentFit                "Fit"           )
      (cons acAlignmentTopLeft            "Top-Left"      )
      (cons acAlignmentTopCenter          "Top-Center"    )
      (cons acAlignmentTopRight           "Top-Right"     )
      (cons acAlignmentMiddleLeft         "Middle-Left"   )
      (cons acAlignmentMiddleCenter       "Middle-Center" )
      (cons acAlignmentMiddleRight        "Middle-Right"  )
      (cons acAlignmentBottomLeft         "Bottom-Left"   )
      (cons acAlignmentBottomCenter       "Bottom-Center" )
      (cons acAlignmentBottomRight        "Bottom-Right"  )
    )
  )

  (setq Attachment
    (list
      (cons acAttachmentPointTopLeft      "Top-Left"      )
      (cons acAttachmentPointTopCenter    "Top-Center"    )
      (cons acAttachmentPointTopRight     "Top-Right"     )
      (cons acAttachmentPointMiddleLeft   "Middle-Left"   )
      (cons acAttachmentPointMiddleCenter "Middle-Center" )
      (cons acAttachmentPointMiddleRight  "Middle-Right"  )
      (cons acAttachmentPointBottomLeft   "Bottom-Left"   )
      (cons acAttachmentPointBottomCenter "Bottom-Center" )
      (cons acAttachmentPointBottomRight  "Bottom-Right"  )
    )
  )  

  ;;-------------------------------------------------------------------------------;;
  ;;                           --=={  Local Functions  }==--                       ;;
  ;;-------------------------------------------------------------------------------;;

  
  ;;  --=={  Error Handler  }==--
  
  (defun *error* ( msg )
    (if cEnt (entdel cEnt))
    (if tEnt (entdel tEnt))

    (if on (mapcar '(lambda ( x ) (vla-put-layeron x :vlax-true)) on))

    (PurgeLayer "LMAC_DINFO")
    
    (or (wcmatch (strcase msg) "*BREAK,*CANCEL*,*EXIT*")
        (princ (strcat "\n** Error: " msg " **")))
    (princ)
  )

  ;.................................................................................;

  (defun _PutDXF ( e x r )
    (entmod (subst (cons x r) (assoc x e) e))
  )

  ;.................................................................................;

  (defun _Update ( e )
    (entupd (cdr (assoc -1 e)))
  )

  ;.................................................................................;

  (defun _Text ( tx ) (strcat "{\\fArial|b1|i0|c0|p34;" tx "}"))

  ;.................................................................................;

  (defun ss->lst ( ss / i ent lst )
    (setq i -1)
    (while (setq ent (ssname ss (setq i (1+ i))))
      (setq lst (cons (vlax-ename->vla-object ent) lst))
    )
    lst
  )

  ;.................................................................................;

  (defun _GetColour ( e / c )    


      "ByLayer"
    
  )

  ;.................................................................................;

  ; (defun _GetScale ( e )
  ;   (vl-princ-to-string
  ;     (mapcar
  ;       (function
  ;         (lambda ( x )
  ;           (rtos (dxf x e) (getvar 'LUNITS) 2)
  ;         )
  ;       )
  ;      '(41 42 43)
  ;     )
  ;   )
  ; )

  ;.................................................................................;

  ; (defun _GetName ( obj )
  ;   (if (vlax-property-available-p obj 'EffectiveName)
  ;     (vla-get-EffectiveName obj)
  ;     (vla-get-name obj)
  ;   )
  ; )

  ;.................................................................................;
  
  ; (defun _GetLW ( e / w )
  ;   (if (setq w (cdr (assoc 370 e)))      
  ;     (cond
  ;       (
  ;         (cdr
  ;           (assoc w
  ;            '(
  ;               (-1 . "ByLayer")
  ;               (-2 . "ByBlock")
  ;               (-3 . "Default")
  ;             )
  ;           )
  ;         )
  ;       )
  ;       ( (strcat (rtos (/ w 100.) 2 2) "mm") )
  ;     )      
  ;     "ByLayer"
  ;   )
  ; )

  ;.................................................................................;

  (defun _Stringify ( data / typ )
    
    (setq data
      (cond
        ( (eq :vlax-true  data) "Yes" )
        ( (eq :vlax-false data) "No"  )
        ( data )
      )
    )
    
    (cond
      ( (eq 'STR (setq typ (type data)))

        data
      )
      ( (eq 'INT typ)

        (itoa data)
      )
      ( (eq 'REAL typ)

        (rtos data)
      )
      ( (vl-princ-to-string data) )
    )
  )

  ;.................................................................................;

  (defun _Display ( Cir Tx ss mode / cObj cSs iObj aStr iLst tStr cnt tStr )
    (setq cObj (vlax-ename->vla-object Cir) aStr "")
    
    (cond
      (
        (or (not ss) (= (sslength ss) 0))
      )
      ( (setq iObj
          (vl-some
            (function
              (lambda ( obj )
                (if (vlax-invoke obj 'IntersectWith cObj acExtendNone) obj)
              )
            )
            (ss->lst ss)
          )
        )

        (setq iLst (entget (vlax-vla-object->ename iObj)))
        (vla-put-Color cObj acRed)

        (cond
          (
            (zerop mode)

            (cond
              (
                ; (eq "INSERT" (dxf 0 iLst))

                ; (if (setq cSs (ssget "_X" (list (cons 0 "INSERT") (cons 2 (_GetName iObj)))))
                ;   (setq cnt (itoa (sslength cSs)))
                ; )

                ; (if (= 1 (dxf 66 iLst))
                ;   (progn
                ;     (setq aStr "\nATTRIBUTES: \n{\\fArial|b0|i0|c0|p34;")

                ;     (foreach x (vlax-invoke iObj 'GetAttributes)
                ;       (setq aStr (strcat aStr (vla-get-TagString x)  ":  " (vla-get-TextString x) "\n"))
                ;     )
                ;     (setq aStr (strcat aStr "}"))
                ;   )
                ; )



(setq test_max (+ (atoi (vlax-get-property iObj 'Linetype)) 10))
                (setq tStr
                  (strcat
                    ;"{\\C2;"         "Noise level" "}"
                    ;"\nNAME:  "      (_GetName iObj)
                    (if cnt (strcat "\nINSTANCES:  " cnt) "")
                    ;"\nLAYER:  "     (dxf 8 iLst)
                    "\\C10;\nMAX:  "  (itoa (atoi (vlax-get-property iObj 'Linetype)))
                    "\\C2\nEQU:  "     (itoa (+ (atoi (vlax-get-property iObj 'Linetype)) equ_level))

                    ;"\nLINEWEIGHT:  "(_GetLW iLst)
                    ;"\nROTATION:  "  (angtos (dxf 50 iLst))
                    ;"\nSCALE:  "     (_GetScale iLst)
                    ;"\nDYNAMIC: "    (_Stringify (vlax-get-property iObj 'isDynamicBlock))
                    ;"\nXREF:  "      (_Stringify (vlax-get-property (vla-item (vla-get-Blocks doc) (_GetName iObj)) 'ISXREF))
                    aStr
                  )
                )
              )
              (t
                (setq tStr (strcat "{\\C2;" "test" "}"))

                (foreach prop
                 '(
                    ; LAYER
                                         LINETYPE
                     COLOR

                    ; LINEWEIGHT
                    ; ALIGNMENT
                    ; ARCLENGTH
                    ; AREA
                    ; ATTACHMENTPOINT
                    ; CENTER
                    ; CIRCUMFERENCE
                    ; CLOSED
                    ; CUSTOMSCALE
                    ; DEGREE
                    ; DIAMETER
                    ; DISPLAYLOCKED
                    ; ELEVATION
                    ; HEIGHT
                    ; LENGTH
                    ; MEASUREMENT
                    ; OBLIQUEANGLE
                    ; RADIUS
                    ; ROTATION
                    ; SCALEFACTOR
                    ; STYLENAME
                    ; TEXTOVERRIDE
                    ; TEXTSTRING
                    ; TOTALANGLE
                    ; WIDTH
                  )

                  (setq tStr
                    (strcat tStr
                      (if
                        (and
                          (vlax-property-available-p iObj prop)
                          (not (eq "" (vlax-get iObj prop)))
                        )

                        (strcat "\n"
                          (strcase (vl-princ-to-string prop)) ":  "

                          (cond
                            (
                              (eq prop 'COLOR)

                              (_GetColour iLst)
                            )
                            ; (
                            ;   (vl-position prop '(DISPLAYLOCKED CLOSED))

                            ;   (_Stringify (vlax-get-property iObj prop))
                            ; )
                            ; (
                            ;   (eq prop 'ALIGNMENT)

                            ;   (cdr (assoc (vlax-get-property iObj prop) Alignment))
                            ; )
                            ; (
                            ;   (eq prop 'ATTACHMENTPOINT)

                            ;   (cdr (assoc (vlax-get-property iObj prop) Attachment))
                            ; )
                            ; (
                            ;   (or
                            ;     (and
                            ;       (eq 'MEASUREMENT prop)
                            ;       (vl-position (vla-get-ObjectName iObj) '("AcDb2LineAngularDimension" "AcDb3PointAngularDimension"))
                            ;     )
                            ;     (and
                            ;       (eq 'TOTALANGLE prop)
                            ;       (eq "AcDbArc" (vla-get-ObjectName iObj))
                            ;     )
                            ;     (eq 'ROTATION prop)
                            ;   )

                            ;   (angtos (vlax-get iObj prop))
                            ; )
                            ;(
                              ;(eq prop 'LINEWEIGHT)

                              ;(_GetLW iLst)
                            ;)
                            (
                              (_Stringify (vlax-get iObj prop))
                            )
                          )
                        )

                        ""
                      )
                    )
                  )
                )
              )
            )

            (_Update
              (_PutDxf
                (_PutDxf (entget tx) 62 251) 1 (_Text tStr)
              )
            )
            t
          )
        )
      )
      (t )
    )
    
    iObj
  )

  ;.................................................................................;

  (defun dxf ( code lst ) (cdr (assoc code lst)))

  ;.................................................................................;

  (defun PurgeLayer ( layer )
    (if
      (not
        (vl-catch-all-error-p
          (setq layer
            (vl-catch-all-apply 'vla-item
              (list
                (vla-get-layers
                  (vla-get-ActiveDocument (vlax-get-acad-object))
                )
                layer
              )
            )
          )
        )
      )      
      (vl-catch-all-apply 'vla-delete (list layer))
    )
  )

  ;.................................................................................;

  (defun RedrawSS ( ss mode )
    (
      (lambda ( i )
        (while (setq e (ssname ss (setq i (1+ i))))
          (redraw e mode)
        )
      )
      -1
    )
  )

  ;;-------------------------------------------------------------------------------;;
  ;;                           --=={  Main Function  }==--                         ;;
  ;;-------------------------------------------------------------------------------;;

  (setq cEnt
    (entmakex
      (list
        (cons 0 "CIRCLE")
        (cons 8 "LMAC_DINFO")
        (cons 10 (getvar 'VIEWCTR))
        (cons 40 (setq rad (/ (getvar 'VIEWSIZE) (float 10))))
        (cons 62 3)
      )
    )
    cELst (entget cEnt)
  )

  (setq tEnt
    (entmakex
      (list
        (cons 0 "MTEXT")                              
        (cons 100 "AcDbEntity")
        (cons 100 "AcDbMText")
        (cons 8   "LMAC_DINFO")
        (cons 1  (_Text (nth DInfo:Mode ModeLst)))
        (cons 10 (getvar 'VIEWCTR))
        (cons 40 (/ (getvar 'VIEWSIZE) 6))
        (cons 50 0.0)
        (cons 62 71)
        (cons 71 1)

        (cons 90 3)
        (cons 63 256)
        (cons 45 1.2)
      )
    )
    tElst (entget tEnt) -pi/4 (/ pi -4.) pi/4 (/ pi 4.) 5pi/4 (/ (* 5 pi) 4.)
  )

  ; (setq msgLst
  ;  '("\n[TAB Mode] [+/- Cursor Size] Move Cursor Over Objects to Retrieve Information..."
  ;    "\n[TAB Mode] [+/- Cursor Size] Click Object to Isolate Layer, Shift+Click to Turn on All Layers..."
  ;   )
  ; )
  
  ;(princ (setq msg (nth DInfo:Mode msgLst)))
  
  (while
    (progn
      (setq gr (grread 't 15 1) code (car gr) data (cadr gr) vs (getvar 'VIEWSIZE))

      (cond
        (
          (and (= 5 code) (listp data))

          (setq r (sqrt (* 2. rad rad)))

          (setq cEnt
            (_Update
              (setq cELst
                (_PutDxf (_PutDxf cELst 10 data) 40 (setq rad (/ vs (float DInfo:cRad))))
              )
            )
          )

          (setq tEnt
            (_Update
              (setq tELst
                (_PutDxf
                  (_PutDxf tELst 10 (polar (polar data -pi/4 rad) 0 (/ vs 90.0))) 40 (/ vs 60.0)
                )
              )
            )
          )

          (if (setq ss (ssget "_C" (polar data  pi/4 r) (polar data 5pi/4 r)))
            (progn

              (ssdel cEnt ss)
              (ssdel tEnt ss)

              (setq Inter (_Display cEnt tEnt ss DInfo:Mode))
            )
          )

          t
        )
       ; (
        ;  (= 2 code)

          ; (cond
          ;   (
          ;     (vl-position data '(43 61))

          ;     (if (> DInfo:cRad 1.0)
          ;       (setq cEnt
          ;         (_Update
          ;           (setq cELst
          ;             (_PutDxf cELst 40
          ;               (setq rad (/ vs (float (setq DInfo:cRad (1- DInfo:cRad)))))
          ;             )
          ;           )
          ;         )
          ;       )

          ;       (princ (strcat "\n** Maximum Cursor Size Reached **" msg))
          ;     )
          ;   )
          ;   (
          ;     (= 45 data)

          ;     (setq cEnt
          ;       (_Update
          ;         (setq cELst
          ;           (_PutDxf cELst 40
          ;             (setq rad (/ vs (float (setq DInfo:cRad (1+ DInfo:cRad)))))
          ;           )
          ;         )
          ;       )
          ;     )
          ;   )
          ;   (
          ;     (= 9 data)

          ;     (setq DInfo:Mode (rem (1+ DInfo:Mode) 2))

          ;     (setq tEnt
          ;       (_Update
          ;         (setq tELst
          ;           (_PutDxf tELst 1 (_Text (nth DInfo:Mode ModeLst)))
          ;         )
          ;       )
          ;     )

          ;     ;(princ (setq msg (nth DInfo:Mode msgLst)))
          ;   )
          ;   (
          ;     (vl-position data '(13 32)) nil
          ;   )
          ;   ( t )
          ; )
        ;)
        ; (
        ;   (and (= 3 code) (listp data) (= 1 DInfo:Mode))

        ;   (if (and Express (acet-sys-shift-down))
        ;     (mapcar
        ;       (function
        ;         (lambda ( x ) (vla-put-layeron x :vlax-true))
        ;       )
        ;       on
        ;     )

        ;     (if (and Inter (not (eq "LMAC_DINFO" (vla-get-layer Inter))))

        ;       (mapcar
        ;         (function
        ;           (lambda ( x )
        ;             (if (not (eq (strcase (vla-get-layer Inter)) (strcase (vla-get-name x))))
        ;               (vla-put-layeron x :vlax-false)
        ;             )
        ;           )
        ;         )
        ;         layers
        ;       )
        ;     )
        ;   )

        ;   t
        ; )
      );; cond




;;;;;;;;;;;; ELEVATOR


;(setq pt1 (getpoint "\rSpecify point <exit>: "))





    ; (setq hgt (getvar 'textsize)
    ;       ocs (trans '(0.0 0.0 1.0) 1 0 t)
    ;       ang (angle '(0.0 0.0) (trans (getvar 'ucsxdir) 0 ocs t))
    ; )
    ; (terpri)

    ; (while (setq pt1 (getpoint "\rSpecify point <exit>: "))
    ;     (setq str (rtos (cadr pt1))
    ;           len (strlen str)
    ;           pt2 (list (car  pt1) (+ (cadr pt1) (* hgt 0.5 (sqrt 3))))
    ;           pt3 (list (- (car pt1) (* hgt len)) (cadr pt2))
    ;           pt4 (list (- (car pt2) (* hgt 0.5 len)) (+ (cadr pt2) hgt))
    ;          ;pt4 (list 1 2 3)
    ;     )
    ;     (foreach sym '(pt1 pt2 pt3 pt4)
    ;         (set sym (trans (eval sym) 1 ocs))
    ;     )




    ;     (entmake
    ;         (list
    ;            '(000 . "LWPOLYLINE")
    ;            '(100 . "AcDbEntity")
    ;            '(100 . "AcDbPolyline")
    ;            '(090 . 3)
    ;            '(070 . 0)
    ;             (cons 038 (caddr pt1))
    ;             (cons 010 pt1)
    ;            '(040 . 0.0)
    ;             (cons 041 hgt)
    ;             (cons 010 pt2)
    ;             (cons 040 (* hgt 0.05))
    ;             (cons 041 (* hgt 0.05))
    ;             (cons 010 pt3)
    ;             (cons 210 ocs)
    ;         )
    ;     )



    ;     (entmake
    ;         (list
    ;            '(000 . "TEXT")
    ;             (cons 007 (getvar 'textstyle))
    ;             (cons 001 str)
    ;             (cons 050 ang)
    ;             (cons 040 hgt)
    ;             (cons 010 pt4)
    ;             (cons 011 pt4)
    ;            '(072 . 1)
    ;            '(073 . 2)
    ;             (cons 210 ocs)
    ;         )
    ;     )








    ; )
;;;;;;; ELEVATOR







    )
  )

  (mapcar 'entdel (list tEnt cEnt))
  (PurgeLayer "LMAC_DINFO")
  
  (princ)
)

;.................................................................................;

; (princ)
 (princ "\n:: DInfo.lsp | Version 1.5 | © Lee Mac 2011 www.lee-mac.com ::")
 (princ "\n:: Type \"DInfo\" to Invoke ::")
(princ)
